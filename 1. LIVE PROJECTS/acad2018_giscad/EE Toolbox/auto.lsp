(defun c:CMD1 ()
(command "NETLOAD" "C:/Program Files/GISCAD2016/EE Toolbox/GISCAD.dll")
(command "NETLOAD" "C:/Program Files/GISCAD2016/EE Toolbox/GISCADU.dll")
(command "NETLOAD" "C:/Program Files/GISCAD2016/EE Toolbox/CopyPastAttr.dll")
(command "NETLOAD" "C:/Program Files/GISCAD2016/EE Toolbox/TitleBlock.dll")
)
