(defun c:ATR (/ com val)
	(initget 1 "Height Angle Style Layer Color")
	(setq com (getkword "\nEnter Command (Height/Angle/Style/Layer/Color): "))
	(setq val (getstring "\nEnter Value: "))
	(prompt "\nSelect Attributes by Crossing Window: ")
	(command ".attedit" "y" "*" "*" "*" "c" pause pause)
	(while (> (getvar "cmdactive") 0)
		(command com val "n")
	)
	(princ)
) 

(defun c:HF ()
	(setq ents (ssget))(command "chprop" ents "" "LA" "features_HIDE" "") 
)

(defun c:DF ()
	(setq ents (ssget))(command "chprop" ents "" "LA" "features_DEL" "") 
)
