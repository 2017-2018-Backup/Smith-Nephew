(setvar "cmdecho" 0)
(princ "\nLoading Smith & Nephew Jobskin for AutoCAD 2018...")
(command "._NETLOAD" "C:/ACAD2018_SMITH-NEPHEW/Interface/SmithNephew.dll")
(LOAD "C:/ACAD2018_SMITH-NEPHEW/LOAD-FILE-EXPLORER.LSP")
(LOAD "C:/ACAD2018_SMITH-NEPHEW/LOAD-A2K-SUPPORT-SITE.LSP")
(LOAD "C:/ACAD2018_SMITH-NEPHEW/SHOW-HIDE-TITLEBLOCK.LSP")
(LOAD "C:/ACAD2018_SMITH-NEPHEW/SHOW-HIDE-LAYERS.LSP")
(princ "\nLoading Complete...")
(setvar "cmdecho" 1)
