;Developed by A2K Technologies 2018
;Layer Filter

(defun C:P1 ()
  (command
    "_.layer"
      "_thaw" "*"
      "_set" "PAGE_1" ; to ensure the one left un-Frozen is one you want on at end
      "_off" "*" "_no"
      "_freeze" "*" ; 
      "_thaw" "PAGE_1,BORDER,TITLE_1,TITLE_2"
      "_on"  "PAGE_1,BORDER,TITLE_1,TITLE_2"
      "" ; complete Layer command
    "_regen" ; in case any of them were Frozen before, and require Regen to show again
  ); command
  (princ)
); defun

(defun C:P2 ()
  (command
    "_.layer"
      "_thaw" "*"
      "_set" "PAGE_2" ; to ensure the one left un-Frozen is one you want on at end
      "_off" "*" "_no"
      "_freeze" "*" ; 
      "_thaw" "PAGE_2,BORDER,TITLE_1"
      "_on"  "PAGE_2,BORDER,TITLE_1"
      "" ; complete Layer command
    "_regen" ; in case any of them were Frozen before, and require Regen to show again
  ); command
  (princ)
); defun

(defun C:P3 ()
  (command
    "_.layer"
      "_thaw" "*"
      "_set" "PAGE_3" ; to ensure the one left un-Frozen is one you want on at end
      "_off" "*" "_no"
      "_freeze" "*" ; 
      "_thaw" "PAGE_3,BORDER,TITLE_1"
      "_on"  "PAGE_3,BORDER,TITLE_1"
      "" ; complete Layer command
    "_regen" ; in case any of them were Frozen before, and require Regen to show again
  ); command
  (princ)
); defun

(defun C:P4 ()
  (command
    "_.layer"
      "_thaw" "*"
      "_set" "PAGE_4" ; to ensure the one left un-Frozen is one you want on at end
      "_off" "*" "_no"
      "_freeze" "*" ; 
      "_thaw" "PAGE_4,BORDER,TITLE_1"
      "_on"  "PAGE_4,BORDER,TITLE_1"
      "" ; complete Layer command
    "_regen" ; in case any of them were Frozen before, and require Regen to show again
  ); command
  (princ)
); defun

(defun C:P5 ()
  (command
    "_.layer"
      "_thaw" "*"
      "_set" "PAGE_5" ; to ensure the one left un-Frozen is one you want on at end
      "_off" "*" "_no"
      "_freeze" "*" ; 
      "_thaw" "PAGE_5,BORDER,TITLE_1"
      "_on"  "PAGE_5,BORDER,TITLE_1"
      "" ; complete Layer command
    "_regen" ; in case any of them were Frozen before, and require Regen to show again
  ); command
  (princ)
); defun

(defun C:P6 ()
  (command
    "_.layer"
      "_thaw" "*"
      "_set" "PAGE_6" ; to ensure the one left un-Frozen is one you want on at end
      "_off" "*" "_no"
      "_freeze" "*" ; 
      "_thaw" "PAGE_6,BORDER,TITLE_1"
      "_on"  "PAGE_6,BORDER,TITLE_1"
      "" ; complete Layer command
    "_regen" ; in case any of them were Frozen before, and require Regen to show again
  ); command
  (princ)
); defun

(defun C:P7 ()
  (command
    "_.layer"
      "_thaw" "*"
      "_set" "PAGE_7" ; to ensure the one left un-Frozen is one you want on at end
      "_off" "*" "_no"
      "_freeze" "*" ; 
      "_thaw" "PAGE_7,BORDER,TITLE_1"
      "_on"  "PAGE_7,BORDER,TITLE_1"
      "" ; complete Layer command
    "_regen" ; in case any of them were Frozen before, and require Regen to show again
  ); command
  (princ)
); defun

(defun C:P8 ()
  (command
    "_.layer"
      "_thaw" "*"
      "_set" "PAGE_8" ; to ensure the one left un-Frozen is one you want on at end
      "_off" "*" "_no"
      "_freeze" "*" ; 
      "_thaw" "PAGE_8,BORDER,TITLE_1"
      "_on"  "PAGE_8,BORDER,TITLE_1"
      "" ; complete Layer command
    "_regen" ; in case any of them were Frozen before, and require Regen to show again
  ); command
  (princ)
); defun

(defun C:P9 ()
  (command
    "_.layer"
      "_thaw" "*"
      "_set" "PAGE_9" ; to ensure the one left un-Frozen is one you want on at end
      "_off" "*" "_no"
      "_freeze" "*" ; 
      "_thaw" "PAGE_9,BORDER,TITLE_1"
      "_on"  "PAGE_9,BORDER,TITLE_1"
      "" ; complete Layer command
    "_regen" ; in case any of them were Frozen before, and require Regen to show again
  ); command
  (princ)
); defun

(defun C:P10 ()
  (command
    "_.layer"
      "_thaw" "*"
      "_set" "PAGE_10" ; to ensure the one left un-Frozen is one you want on at end
      "_off" "*" "_no"
      "_freeze" "*" ; 
      "_thaw" "PAGE_10,BORDER,TITLE_1"
      "_on"  "PAGE_10,BORDER,TITLE_1"
      "" ; complete Layer command
    "_regen" ; in case any of them were Frozen before, and require Regen to show again
  ); command
  (princ)
); defun

(defun C:P11 ()
  (command
    "_.layer"
      "_thaw" "*"
      "_set" "PAGE_11" ; to ensure the one left un-Frozen is one you want on at end
      "_off" "*" "_no"
      "_freeze" "*" ; 
      "_thaw" "PAGE_11,BORDER,TITLE_1"
      "_on"  "PAGE_11,BORDER,TITLE_1"
      "" ; complete Layer command
    "_regen" ; in case any of them were Frozen before, and require Regen to show again
  ); command
  (princ)
); defun

(defun C:P12 ()
  (command
    "_.layer"
      "_thaw" "*"
      "_set" "PAGE_12" ; to ensure the one left un-Frozen is one you want on at end
      "_off" "*" "_no"
      "_freeze" "*" ; 
      "_thaw" "PAGE_12,BORDER,TITLE_1"
      "_on"  "PAGE_12,BORDER,TITLE_1"
      "" ; complete Layer command
    "_regen" ; in case any of them were Frozen before, and require Regen to show again
  ); command
  (princ)
); defun

(defun C:P13 ()
  (command
    "_.layer"
      "_thaw" "*"
      "_set" "PAGE_13" ; to ensure the one left un-Frozen is one you want on at end
      "_off" "*" "_no"
      "_freeze" "*" ; 
      "_thaw" "PAGE_13,BORDER,TITLE_1"
      "_on"  "PAGE_13,BORDER,TITLE_1"
      "" ; complete Layer command
    "_regen" ; in case any of them were Frozen before, and require Regen to show again
  ); command
  (princ)
); defun

(defun C:P14 ()
  (command
    "_.layer"
      "_thaw" "*"
      "_set" "PAGE_14" ; to ensure the one left un-Frozen is one you want on at end
      "_off" "*" "_no"
      "_freeze" "*" ; 
      "_thaw" "PAGE_14,BORDER,TITLE_1"
      "_on"  "PAGE_14,BORDER,TITLE_1"
      "" ; complete Layer command
    "_regen" ; in case any of them were Frozen before, and require Regen to show again
  ); command
  (princ)
); defun

(defun C:P15 ()
  (command
    "_.layer"
      "_thaw" "*"
      "_set" "PAGE_15" ; to ensure the one left un-Frozen is one you want on at end
      "_off" "*" "_no"
      "_freeze" "*" ; 
      "_thaw" "PAGE_15,BORDER,TITLE_1"
      "_on"  "PAGE_15,BORDER,TITLE_1"
      "" ; complete Layer command
    "_regen" ; in case any of them were Frozen before, and require Regen to show again
  ); command
  (princ)
); defun

(defun C:LAYER_ON ()
  (command
    "_.layer"
      "_thaw" "*"
      "_set" "PAGE_1" ; to ensure the one left un-Frozen is one you want on at end
      "_off" "*" "_no"
      "_on"  "PAGE_1,BORDER,TITLE_1,TITLE_2"
      "" ; complete Layer command
    "_regen" ; in case any of them were Frozen before, and require Regen to show again
  ); command
  (princ)
); defun

(defun C:SAVEME ()
	(COMMAND "QSAVE")
	(princ)
)
