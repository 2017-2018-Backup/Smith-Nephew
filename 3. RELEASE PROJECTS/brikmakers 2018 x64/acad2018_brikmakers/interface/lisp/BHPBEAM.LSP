(defun newerr (st)
	     (if (/= st "Function cancelled")
	          (princ (strcat "\nGeneral Error : " st)))
	     (princ "\n\nSystem Restored ... \n\n")
	     (setq *error* nil)
	         (princ)
	)

	;(prompt "\nLoading BHPBEAM draw program......")
	
	(defun c:BHPbeam (/ ccol elay)
	  	;(setq fname "bhp_wb.dat")
	  	;(setq val "0")
	  	(setq file_name (strcat "C:/ACAD2018_BRIKMAKERS/Interface/Lisp/bhpbeam/" fname) )
		(setvar "osmode" 0)
		(setq elay (getvar "CLAYER"))            ; save current layer
		(setq ccol (getvar "CECOLOR"))           ; save current color
		(load "C:/ACAD2018_BRIKMAKERS/Interface/Lisp/bhpbeam/bhpbeam.dat")
		(setq *error* newerr)
		(setq scale (getvar "dimscale"))
		(setq bhp_dialog (load_dialog "C:/ACAD2018_BRIKMAKERS/Interface/Lisp/bhpbeam"))
;;;		(new_dialog "bhp" bhp_dialog) 
;;;		(set_actions) 
		(if file_name 
			(progn
				(setq fd (open file_name "r"))
				(repeat (1+ (atoi val)) 
					(setq code_line (read-line fd))
				) 
				(close fd)
			)
		) 
		(if (/= code_line "") 
			(progn
				(chk_bhp_sect) 
				(bm_ins) 
				(draw_bhp_sect) 
				(unload_dialog bhp_dialog)
			) 
			(progn
				(princ "No beam selected") 
				(princ)
			)
		)
		(setq *error* nil)
		(setvar "CLAYER"    elay)
		(setvar "CECOLOR"   ccol)
		(princ)
	)

	(defun set_actions () 
		(action_tile "bhp_wb" 
			"(progn
				(setq file_name \"C:/ACAD2018_BRIKMAKERS/Interface/Lisp/bhpbeam/bhp_wb.dat\")
				(setq diag_type \"bhp1_list\")
				(bhp_sect)
			)"
		) 
		(action_tile "bhp_wc" 
			"(progn
				(setq file_name \"C:/ACAD2018_BRIKMAKERS/Interface/Lisp/bhpbeam/bhp_wc.dat\")
			    	(setq diag_type \"bhp1_list\")			
				(bhp_sect)
			)"
		) 
		(action_tile "bhp_ub" 
			"(progn
				(setq file_name \"C:/ACAD2018_BRIKMAKERS/Interface/Lisp/bhpbeam/bhp_ub.dat\")
				(setq diag_type \"bhp1_list\")      
				(bhp_sect)
			)"
		) 
		(action_tile "bhp_uc" 
			"(progn
				(setq file_name \"C:/ACAD2018_BRIKMAKERS/Interface/Lisp/bhpbeam/bhp_uc.dat\")
				(setq diag_type \"bhp1_list\")
				(bhp_sect)
			)"
		) 
		(action_tile "bhp_pfc" 
			"(progn
				(setq file_name \"C:/ACAD2018_BRIKMAKERS/Interface/Lisp/bhpbeam/bhp_pfc.dat\")
				(setq diag_type \"bhp1_list\")
				(bhp_sect)
			)"
		) 
		(action_tile "bhp_tfb" 
			"(progn
				(setq file_name \"C:/ACAD2018_BRIKMAKERS/Interface/Lisp/bhpbeam/bhp_tfb.dat\")
				(setq diag_type \"bhp1_list\")
				(bhp_sect)
			)"
		) 
		(action_tile "bhp_tfc" 
			"(progn
				(setq file_name \"C:/ACAD2018_BRIKMAKERS/Interface/Lisp/bhpbeam/bhp_tfc.dat\")
				(setq diag_type \"bhp1_list\")
				(bhp_sect)
			)"
		) 
		(action_tile "bhp_chs" 
			"(progn
				(setq file_name \"C:/ACAD2018_BRIKMAKERS/Interface/Lisp/bhpbeam/bhp_chs.dat\")
				(setq diag_type \"bhp2_list\")
				(bhp_sect)
			)"
		) 
		(action_tile "bhp_rhs" 
			"(progn
				(setq file_name \"C:/ACAD2018_BRIKMAKERS/Interface/Lisp/bhpbeam/bhp_rhs.dat\")
				(setq diag_type \"bhp2_list\")
				(bhp_sect)
			)"
		) 
		(action_tile "bhp_shs" 
			"(progn
				(setq file_name \"C:/ACAD2018_BRIKMAKERS/Interface/Lisp/bhpbeam/bhp_shs.dat\")
				(setq diag_type \"bhp2_list\")
				(bhp_sect)
			)"
		) 
		(action_tile "bhp_ea" 
			"(progn
				(setq file_name \"C:/ACAD2018_BRIKMAKERS/Interface/Lisp/bhpbeam/bhp_ea.dat\")
				(setq diag_type \"bhp2_list\")
				(bhp_sect)
			)"
		) 
		(action_tile "bhp_ua" 
			"(progn
				(setq file_name \"C:/ACAD2018_BRIKMAKERS/Interface/Lisp/bhpbeam/bhp_ua.dat\")
				(setq diag_type \"bhp2_list\")
				(bhp_sect)
			)"
		) 
		(action_tile "bhp_lcp" 
			"(progn
				(setq file_name \"C:/ACAD2018_BRIKMAKERS/Interface/Lisp/bhpbeam/bhp_lcp.dat\")
				(setq diag_type \"bhp1_list\")
				(bhp_sect)
			)"
		) 
		(action_tile "bhp_lzp" 
			"(progn
				(setq file_name \"C:/ACAD2018_BRIKMAKERS/Interface/Lisp/bhpbeam/bhp_lzp.dat\")
				(setq diag_type \"bhp1_list\")
				(bhp_sect)
			)"
		) 
		  (action_tile "cancel" "(done_dialog 0)") 
		  (c_ont_dialog)
	)

	(defun bhp_sect () 
		(setq fd (open file_name "r"))
		(new_dialog diag_type bhp_dialog) 
		(start_list "list_box") 
		(while (setq line (read-line fd))
			(setq box_val (substr line 1 24))
			(add_list box_val)
		) 
		(end_list) 
		(action_tile "list_box" "(setq val $value)") 
		(start_dialog)
	)

	(defun getdim (b_l l_l) 
		(atoi (substr code_line b_l l_l))
	)

	(defun chk_bhp_sect ()
	  (setq chk_name (vl-filename-base file_name))
	  (cond
	    ((or (= chk_name "bhp_ub") (= chk_name "bhp_uc")) (ubucdims)) 
	    ((or (= chk_name "bhp_wb") (= chk_name "bhp_wc")) (ubucdims)) 
	    ((= chk_name "bhp_pfc") (pfcdims)) 
	    ((= chk_name "bhp_tfc") (tfcdims)) 
	    ((= chk_name "bhp_tfb") (tfbdims)) 
	    ((or (= chk_name "bhp_ea") (= chk_name "bhp_ua")) (angldims)) 
	    ((or (= chk_name "bhp_shs") (= chk_name "bhp_rhs")) (rhsdims)) 
	    ((= chk_name "bhp_chs") (chsdims)) 
	    ((or (= chk_name "bhp_lcp") (= chk_name "bhp_lzp")) (lysdims))
	  )
	)

	(defun ubucdims () 
		(setq bd (getdim 25 5) 
		fw (getdim 30 4) 
		ft (getdim 34 3) 
		wt (getdim 37 3) 
		rr (getdim 40 3))
		(if (= rr 0) 
		(setq rr 0.1)
		) 
		(setq hbd (/ bd 2.0) 
		rd (sqrt (+ (* rr rr) (* rr rr))) 
		hfw (- (/ fw 2.0) (+ (/ wt 2) rr)) 
		wd (- bd (+ (* ft 2) (* rr 2))))
	)

	(defun pfcdims () 
	  (setq bd (getdim 25 4) 
	        fw (getdim 29 4) 
	        ft (getdim 33 3) 
	        wt (getdim 36 3) 
	        rr (getdim 39 3) 
	        gge (getdim 42 3) 
	        cy (getdim 42 3) 
	        hbd (/ bd 2.0) 
	        rd (sqrt (+ (* rr rr) (* rr rr))) 
	        wd (- bd (+ (* ft 2) (* rr 2))) 
	        cfw (- fw (+ wt rr)))
	)

	(defun tfcdims () 
	  (setq bd (getdim 25 4) 
	        fw (getdim 29 3) 
	        ft (getdim 32 4) 
	        wt (getdim 36 2) 
	        rr (getdim 38 2) 
	        tr (getdim 40 2) 
	        wd (getdim 42 5) 
	        gge (getdim 47 3) 
	        cy (getdim 50 3) 
	        ffw (- fw wt) 
	        rd (sqrt (+ (* rr rr) (* rr rr))) 
	        trd (sqrt (+ (* tr tr) (* tr tr))) 
	        hf (/ (- fw wt) 2) 
	        hfw (+ hf wt) 
	        ris (atan (dtr 5)) 
	        hflr (* ris hf) 
	        flr (* hflr 2) 
	        tth (- ft hflr) 
	        wd (- bd (* (+ tth flr) 2)) 
	        slfw (sqrt (+ (* ffw ffw) (* flr flr))))
	)

	(defun tfbdims () 
	  (setq bd (getdim 25 4) 
	        fw (getdim 29 3) 
	        ft (getdim 32 4) 
	        wt (getdim 36 2) 
	        rr (getdim 38 2) 
	        tr (getdim 40 2) 
	        wd (getdim 42 2) 
	        hbd (/ bd 2.0) 
	        hfw (/ fw 2.0) 
	        rd (sqrt (+ (* rr rr) (* rr rr))) 
	        wd (- bd (+ (* ft 2) (* rr 2))) 
	        ffw (- hfw (/ wt 2)) 
	        ris (atan (dtr 5)) 
	        hffw (/ ffw 2.0) 
	        hflr (* ris hffw) 
	        flr (* hflr 2) 
	        tth (- ft hflr) 
	        wd (- bd (* (+ tth flr) 2)) 
	        slfw (sqrt (+ (* ffw ffw) (* flr flr))))
	)

	(defun angldims () 
		(setq al (getdim 25 4) 
		bl (getdim 29 4) 
		th (getdim 33 3) 
		rr (getdim 36 3) 
		tr (getdim 39 3) 
		ggea (getdim 41 4) 
		ggeb (getdim 45 4) 
		cx (getdim 49 3) 
		cy (getdim 52 3) 
		rd (sqrt (+ (* rr rr) (* rr rr))) 
		trd (sqrt (+ (* tr tr) (* tr tr))) 
		thd (- th tr) 
		laa (- al (+ (+ th rr) tr)) 
		lab (- bl (+ (+ th rr) tr)))
	)

	(defun chsdims () 
		(setq bd (getdim 25 4) 
		th (getdim 29 3) 
		fw bd 
		o_r (/ bd 2.0) 
		i_r (- o_r th))
	)

	(defun rhsdims () 
		(setq bd (getdim 25 4) 
		fw (getdim 29 4) 
		th (getdim 33 3) 
		rr (* 0.8 th) 
		tr (* 2 th))
	)

(defun lysdims () 
  (setq bd (getdim 25 4) 
        fw (getdim 29 3) 
        ft (getdim 32 3) 
        wt (getdim 35 3))
) 
(defun bm_ins () 
  (new_dialog "det_cen" bhp_dialog) 
  (setq bmview "S" d_o 
        1 c_o 
        0)
  (set_tile "s_ect" "1") 
  (set_tile "f_det" "1") 
  (set_tile "cl_of" "1") 
  (action_tile "s_ect" "(setq bmview \"S\")") 
  (action_tile "p_lan" "(setq bmview \"P\")") 
  (action_tile "e_lev" "(setq bmview \"E\")") 
  (action_tile "f_det" "(setq d_o 1)") 
  (action_tile "d_det" "(setq d_o 0)") 
  (action_tile "cl_on" "(setq c_o 1)") 
  (action_tile "cl_of" "(setq c_o 0)") 
  (action_tile "cancel" "(done_dialog 0)") 
  (c_ont_dialog)
) 
(defun draw_bhp_sect () 
  (setq ck_1 0 
        ck_2 0 
        ck_3 0 
        ck_4 0 
        ck_5 0 
        ck_6 0)
  (cond
    ((and (= bmview "S") 
       (or (= chk_name "bhp_uc") (= chk_name "bhp_ub"))
     ) 
     (ubucsect)
    ) 
    ((and (= bmview "P") 
       (or (= chk_name "bhp_uc") (= chk_name "bhp_ub"))
     ) 
     (ubucplan)
    ) 
    ((and (= bmview "E") 
       (or (= chk_name "bhp_uc") (= chk_name "bhp_ub"))
     ) 
     (ubucelev)
    ) 
    ((and (= bmview "S") 
       (or (= chk_name "bhp_wc") (= chk_name "bhp_wb"))
     ) 
     (ubucsect)
    ) 
    ((and (= bmview "P") 
       (or (= chk_name "bhp_wc") (= chk_name "bhp_wb"))
     ) 
     (ubucplan)
    ) 
    ((and (= bmview "E") 
       (or (= chk_name "bhp_wc") (= chk_name "bhp_wb"))
     ) 
     (ubucelev)
    ) 
    ((and (= bmview "S") 
       (= chk_name "bhp_pfc")
     ) 
     (pfcsect)
    ) 
    ((and (= bmview "P") 
       (= chk_name "bhp_pfc")
     ) 
     (pfcplan)
    ) 
    ((and (= bmview "E") 
       (= chk_name "bhp_pfc")
     ) 
     (pfcelev)
    ) 
    ((and (= bmview "S") 
       (= chk_name "bhp_tfc")
     ) 
     (tfcsect)
    ) 
    ((and (= bmview "P") 
       (= chk_name "bhp_tfc")
     ) 
     (pfcplan)
    ) 
    ((and (= bmview "E") 
       (= chk_name "bhp_tfc")
     ) 
     (pfcelev)
    ) 
    ((and (= bmview "S") 
       (= chk_name "bhp_tfb")
     ) 
     (tfbsect)
    ) 
    ((and (= bmview "P") 
       (= chk_name "bhp_tfb")
     ) 
     (ubucplan)
    ) 
    ((and (= bmview "E") 
       (= chk_name "bhp_tfb")
     ) 
     (ubucelev)
    ) 
    ((and (= bmview "S") 
       (or (= chk_name "bhp_ea") (= chk_name "bhp_ua"))
     ) 
     (angsect)
    ) 
    ((and (= bmview "P") 
       (or (= chk_name "bhp_ea") (= chk_name "bhp_ua"))
     ) 
     (angelev)
    ) 
    ((and (= bmview "E") 
       (or (= chk_name "bhp_ea") (= chk_name "bhp_ua"))
     ) 
     (angelev)
    ) 
    ((and (= bmview "S") 
       (= chk_name "bhp_chs")
     ) 
     (chssect)
    ) 
    ((and (= bmview "S") 
       (or (= chk_name "bhp_rhs") (= chk_name "bhp_shs"))
     ) 
     (rhssect)
    ) 
    ((and (= bmview "P") 
       (or (= chk_name "bhp_rhs") (= chk_name "bhp_shs") (= chk_name "bhp_chs"))
     ) 
     (rhselev)
    ) 
    ((and (= bmview "E") 
       (or (= chk_name "bhp_rhs") (= chk_name "bhp_shs") (= chk_name "bhp_chs"))
     ) 
     (rhselev)
    ) 
    ((and (= bmview "S") 
       (= chk_name "bhp_lcp")
     ) 
     (lyscsect)
    ) 
    ((and (= bmview "P") 
       (= chk_name "bhp_lcp")
     ) 
     (lyscplan)
    ) 
    ((and (= bmview "E") 
       (= chk_name "bhp_lcp")
     ) 
     (pfcelev)
    ) 
    ((and (= bmview "S") 
       (= chk_name "bhp_lzp")
     ) 
     (lyszsect)
    ) 
    ((and (= bmview "P") 
       (= chk_name "bhp_lzp")
     ) 
     (lyszplan)
    ) 
    ((and (= bmview "E") 
       (= chk_name "bhp_lzp")
     ) 
     (lyszelev)
    )
  )
) 
(defun dtr (ang) 
  (* pi (/ ang 180.0))
) 
(defun rotang () 
  (setq ang90 (+ ang (dtr 90)) 
        ang270 (+ ang (dtr 270)) 
        ang180 (+ ang (dtr 180)) 
        ang45 (+ ang (dtr 45)) 
        ang135 (+ ang (dtr 135)) 
        ang225 (+ ang (dtr 225)) 
        ang315 (+ ang (dtr 315)) 
        ang5 (+ ang (dtr 5)) 
        ang175 (+ ang (dtr 175)) 
        ang185 (+ ang (dtr 185)) 
        ang355 (+ ang (dtr 355)))
) 
(defun ubucsect (/ ip p1 p2 p3 p4 p5 p6 p7 p8 p9 p10 p11 p12 p13 p14 p15) 
  (setq ip "TC")
  (bm_ip) 
  (setq cp (getpoint "\nLocation of beam:") 
        ang (dtr 90))
  (rotang) 
  (cond
    ((= ip "TL") (setq sp (polar cp ang fw))) 
    ((= ip "TC") (setq sp (polar cp ang (/ fw 2.0)))) 
    ((= ip "TR") (setq sp cp)) 
    ((= ip "ML") (setq sp (polar (polar cp ang90 (/ bd 2.0)) ang fw))) 
    ((= ip "MC") (setq sp (polar (polar cp ang90 (/ bd 2.0)) ang (/ fw 2.0)))) 
    ((= ip "MR") (setq sp (polar cp ang90 (/ bd 2.0)))) 
    ((= ip "BL") (setq sp (polar (polar cp ang90 bd) ang fw))) 
    ((= ip "BC") (setq sp (polar (polar cp ang90 bd) ang (/ fw 2.0)))) 
    ((= ip "BR") (setq sp (polar cp ang90 bd)))
  ) 
  (setq p1 (polar sp ang270 ft) 
        p2 (polar p1 ang180 hfw) 
        p3 (polar p2 ang225 rd) 
        p4 (polar p3 ang270 wd) 
        p5 (polar p4 ang315 rd) 
        p6 (polar p5 ang hfw) 
        p7 (polar p6 ang270 ft) 
        p8 (polar p7 ang180 fw) 
        p9 (polar p8 ang90 ft) 
        p10 (polar p9 ang hfw) 
        p11 (polar p10 ang45 rd) 
        p12 (polar p11 ang90 wd) 
        p13 (polar p12 ang135 rd) 
        p14 (polar p13 ang180 hfw) 
        p15 (polar p14 ang90 ft))
  (marklent) 
  (if (= c_o 1) 
    (progn
      (setq cl_s (polar (polar sp ang180 (/ fw 2.0)) ang90 (* (getvar "dimscale") 
                                                            10
                                                         )
                 ) 
            cl_e (polar cl_s ang270 (+ bd (* (getvar "dimscale") 20))))
      (setline "$cl") 
      (command "line" cl_s cl_e "")
    )
  ) 
  (setline "$ol") 
  (if (= d_o 1) 
    (command "pline" sp "W" "0" "0" p1 p2 "a" p3 "l" p4 "a" p5 "l" p6 p7 p8 p9 
             p10 "a" p11 "l" p12 "a" p13 "l" p14 p15 "c"
    )
  ) 
  (if (= d_o 0) 
    (progn
      (setq p16 (polar p15 ang (/ fw 2.0)) 
            p17 (polar p16 ang270 bd))
      (command "line" p15 sp "" "line" p8 p7 "" "line" p16 p17 "")
    )
  ) 
  (selsince) 
  (rotsect)
) 
(defun ubucelev (/ p1 p2 p3 p4 p5 p6) 
  (setq ip "T" ck_2 
        1 ck_3 
        1 ck_4 
        1 ck_5 
        1 ck_6 
        1)
  (mem_loc) 
  (setq sp (getpoint "\nStart point of beam:") 
        ep (getpoint sp "\nEnd point of beam:") 
        ang (angle sp ep) 
        cl_s sp 
        cl_e ep)
  (rotang) 
  (if (= ip "T") 
    (setq sp sp)
  ) 
  (if (= ip "C") 
    (progn
      (setq sp (polar sp ang90 (/ bd 2.0)) 
            ep (polar ep ang90 (/ bd 2.0)))
    )
  ) 
  (if (= ip "B") 
    (progn
      (setq sp (polar sp ang90 bd) 
            ep (polar ep ang90 bd))
    )
  ) 
  (setq p1 (polar ep ang270 bd) 
        p2 (polar sp ang270 bd) 
        p3 (polar p2 ang90 ft) 
        p4 (polar p1 ang90 ft) 
        p5 (polar sp ang270 ft) 
        p6 (polar ep ang270 ft))
  (if (= c_o 1 1) 
    (progn
      (setq cl_s (polar cl_s ang180 (* (getvar "dimscale") 15)) 
            cl_e (polar cl_e ang (* (getvar "dimscale") 15)))
      (setline "$cl") 
      (command "line" cl_s cl_e "")
    )
  ) 
  (setline "$ol") 
  (command "line" sp ep p1 p2 "C") 
  (if (= d_o 1) 
    (command "line" p5 p6 "" "line" p3 p4 "")
  )
) 
(defun ubucplan (/ sp ep p1 p2 p3 p4 p5 p6) 
  (setq ip "T" ck_2 
        1 ck_3 
        1 ck_4 
        1 ck_5 
        1 ck_6 
        1)
  (mem_loc) 
  (setq sp (getpoint "\nStart point of beam:") 
        ep (getpoint sp "\nEnd point of beam:") 
        ang (angle sp ep) 
        cl_s sp 
        cl_e ep)
  (rotang) 
  (if (= ip "T") 
    (setq sp sp)
  ) 
  (if (= ip "C") 
    (progn
      (setq sp (polar sp ang90 (/ fw 2.0)) 
            ep (polar ep ang90 (/ fw 2.0)))
    )
  ) 
  (if (= ip "B") 
    (progn
      (setq sp (polar sp ang90 fw) 
            ep (polar ep ang90 fw))
    )
  ) 
  (setq p1 (polar ep ang270 fw) 
        p2 (polar sp ang270 fw) 
        p3 (polar p2 ang90 (/ (- fw wt) 2)) 
        p4 (polar p1 ang90 (/ (- fw wt) 2)) 
        p5 (polar sp ang270 (/ (- fw wt) 2)) 
        p6 (polar ep ang270 (/ (- fw wt) 2)))
  (if (= c_o 1 1) 
    (progn
      (setq cl_s (polar cl_s ang180 (* (getvar "dimscale") 15)) 
            cl_e (polar cl_e ang (* (getvar "dimscale") 15)))
      (setline "$cl") 
      (command "line" cl_s cl_e "")
    )
  ) 
  (setline "$ol") 
  (command "line" sp ep p1 p2 "C") 
  (if (= d_o 1) 
    (progn
      (setline "$hl") 
      (command "line" p5 p6 "" "line" p3 p4 "")
    )
  )
) 
(defun pfcsect (/ ip td sp ep p1 p2 p3 p4 p5 p6 p7 p8 p9) 
  (setq ip "T" td "R" 
        ck_2 1 
        ck_3 1 
        ck_4 1 
        ck_6 1)
  (mem_loc) 
  (setq cp (getpoint "\nLocation of beam:") 
        ang (dtr 90))
  (rotang) 
  (cond
    ((= ip "T") (setq sp cp)) 
    ((= ip "C") (setq sp (polar cp ang90 (/ bd 2.0)))) 
    ((= ip "B") (setq sp (polar cp ang90 bd)))
  ) 
  (if (= td "R") 
    (progn
      (setq p1 (polar sp ang fw) 
            p2 (polar p1 ang270 ft) 
            p3 (polar p2 ang180 cfw) 
            p4 (polar p3 ang225 rd) 
            p5 (polar p4 ang270 wd) 
            p6 (polar p5 ang315 rd) 
            p7 (polar p6 ang cfw) 
            p8 (polar p7 ang270 ft) 
            p9 (polar p8 ang180 fw))
      (marklent)
    )
  ) 
  (if (= td "L") 
    (progn
      (setq p1 (polar sp ang180 fw) 
            p2 (polar p1 ang270 ft) 
            p3 (polar p2 ang cfw) 
            p4 (polar p3 ang315 rd) 
            p5 (polar p4 ang270 wd) 
            p6 (polar p5 ang225 rd) 
            p7 (polar p6 ang180 cfw) 
            p8 (polar p7 ang270 ft) 
            p9 (polar p8 ang fw))
      (marklent)
    )
  ) 
  (setline "$ol") 
  (if (= d_o 1) 
    (command "pline" sp "W" "0" "0" p1 p2 p3 "a" p4 "l" p5 "a" p6 "l" p7 p8 p9 
           "c"
    )
  ) 
  (if (= d_o 0) 
    (command "pline" p1 "W" "0" "0" sp p9 p8 "")
  ) 
  (selsince) 
  (rotsect)
) 
(defun pfcelev (/ p1 p2 p3 p4 p5 p6) 
  (setq ip "T" ta "A" 
        ck_2 1 
        ck_3 1 
        ck_5 1 
        ck_6 1)
  (if (= d_o 0) 
    (setq ck_4 1)
  ) 
  (mem_loc) 
  (setq sp (getpoint "\nStart point of beam:") 
        ep (getpoint sp "\nEnd point of beam:") 
        ang (angle sp ep) 
        cl_s sp 
        cl_e ep)
  (rotang) 
  (if (= ip "T") 
    (setq sp sp)
  ) 
  (if (= ip "C") 
    (progn
      (setq sp (polar sp ang90 (/ bd 2.0)) 
            ep (polar ep ang90 (/ bd 2.0)))
    )
  ) 
  (if (= ip "B") 
    (progn
      (setq sp (polar sp ang90 bd) 
            ep (polar ep ang90 bd))
    )
  ) 
  (setq p1 (polar ep ang270 bd) 
        p2 (polar sp ang270 bd) 
        p3 (polar p2 ang90 ft) 
        p4 (polar p1 ang90 ft) 
        p5 (polar sp ang270 ft) 
        p6 (polar ep ang270 ft))
  (if (= c_o 1) 
    (progn
      (setq cl_s (polar cl_s ang180 (* (getvar "dimscale") 15)) 
            cl_e (polar cl_e ang (* (getvar "dimscale") 15)))
      (command "layer" "s" b#_cl "" "line" cl_s cl_e "")
    )
  ) 
  (if (= ta "A") 
    (progn
      (setline "$ol") 
      (command "line" sp ep p1 p2 "C") 
      (if (= d_o 1) 
        (progn
          (setline "$hl") 
          (command "line" p5 p6 "" "line" p3 p4 "")
        )
      )
    )
  ) 
  (if (= ta "T") 
    (progn
      (setline "$ol") 
      (command "line" sp ep p1 p2 "C") 
      (if (= d_o 1) 
        (command "line" p5 p6 "" "line" p3 p4 "")
      )
    )
  )
) 
(defun pfcplan (/ td ip sp ep P1 P2 P3 P4) 
  (setq ip "B" td "U" 
        ck_1 1 
        ck_4 1 
        ck_5 1 
        ck_6 1)
  (if (= d_o 0) 
    (setq ck_3 1)
  ) 
  (mem_loc) 
  (setq sp (getpoint "\nStart point of beam:") 
        ep (getpoint sp "\nEnd point of beam:") 
        ang (angle sp ep) 
        cl_s sp 
        cl_e ep)
  (rotang) 
  (if (= c_o 1 1) 
    (progn
      (setq cl_s (polar cl_s ang180 (* (getvar "dimscale") 15)) 
            cl_e (polar cl_e ang (* (getvar "dimscale") 15)))
      (setline "$cl") 
      (command "line" cl_s cl_e "")
    )
  ) 
  (if (= td "U") 
    (progn
      (if (and (= td "U") 
            (= ip "B")
          ) 
        (setq sp sp)
      ) 
      (if (and (= td "U") 
            (= ip "C")
          ) 
        (progn
          (setq sp (polar sp ang270 cy) 
                ep (polar ep ang270 cy))
        )
      ) 
      (if (and (= td "U") 
            (= ip "G")
          ) 
        (progn
          (setq sp (polar sp ang270 gge) 
                ep (polar ep ang270 gge))
        )
      ) 
      (setq p1 (polar sp ang90 fw) 
            p2 (polar ep ang90 fw) 
            p3 (polar sp ang90 wt) 
            p4 (polar ep ang90 wt))
      (setline "$ol") 
      (command "line" sp p1 p2 ep "C") 
      (if (= d_o 1) 
        (progn
          (setline "$hl") 
          (command "line" p3 p4 "")
        )
      )
    )
  ) 
  (if (= td "D") 
    (progn
      (if (and (= td "D") 
            (= ip "B")
          ) 
        (setq sp sp)
      ) 
      (if (and (= td "D") 
            (= ip "C")
          ) 
        (progn
          (setq sp (polar sp ang90 cy) 
                ep (polar ep ang90 cy))
        )
      ) 
      (if (and (= td "D") 
            (= ip "G")
          ) 
        (progn
          (setq sp (polar sp ang90 gge) 
                ep (polar ep ang90 gge))
        )
      ) 
      (setq p1 (polar sp ang270 fw) 
            p2 (polar ep ang270 fw) 
            p3 (polar sp ang270 wt) 
            p4 (polar ep ang270 wt))
      (setline "$ol") 
      (command "line" sp p1 p2 ep "C") 
      (if (= d_o 1) 
        (progn
          (setline "$hl") 
          (command "line" p3 p4 "")
        )
      )
    )
  )
) 
(defun angsect (/ ip td sp p1 p2 p3 p4 p5 p6 p7 p8) 
  (setq ip "B" td "R" 
        ck_1 1 
        ck_3 1 
        ck_4 1 
        ck_6 1)
  (mem_loc) 
  (setq cp (getpoint "\nLocation of angle:") 
        ang (dtr 90))
  (rotang) 
  (cond
    ((= ip "B") (setq sp cp)) 
    ((= ip "G") (setq sp (polar cp ang270 ggea))) 
    ((= ip "C") (setq sp (polar cp ang270 cx)))
  ) 
  (if (= td "R") 
    (progn
      (setq p1 (polar sp ang bl) 
            p2 (polar p1 ang90 thd) 
            p3 (polar p2 ang135 trd) 
            p4 (polar p3 ang180 lab) 
            p5 (polar p4 ang135 rd) 
            p6 (polar p5 ang90 laa) 
            p7 (polar p6 ang135 trd) 
            p8 (polar p7 ang180 thd))
      (marklent)
    )
  ) 
  (if (= td "L") 
    (progn
      (setq p1 (polar sp ang180 bl) 
            p2 (polar p1 ang90 thd) 
            p3 (polar p2 ang45 trd) 
            p4 (polar p3 ang lab) 
            p5 (polar p4 ang45 rd) 
            p6 (polar p5 ang90 laa) 
            p7 (polar p6 ang45 trd) 
            p8 (polar p7 ang thd))
      (marklent)
    )
  ) 
  (setline "$ol") 
  (if (= d_o 1) 
    (command "pline" sp "W" "0" "0" p1 p2 "a" p3 "l" p4 "a" p5 "l" p6 "a" p7 "l" 
             p8 "c"
    )
  ) 
  (if (= d_o 0) 
    (command "pline" p1 "W" "0" "0" sp p8 "")
  ) 
  (selsince) 
  (rotsect)
) 
(defun angelev (/ td ip ta lgtp sp ep p1 p2 p3 p4) 
  (setq ip "B" td "U" 
        ta "A" lgtp "L" 
        ck_1 1 
        ck_5 1 
        ck_6 1)
  (if (= chk_name "bhp_ua") 
    (setq ck_6 0)
  ) 
  (mem_loc) 
  (setq sp (getpoint "\nStart point of angle:") 
        ep (getpoint sp "\nEnd point of angle:") 
        ang (angle sp ep) 
        cl_s sp 
        cl_e ep)
  (rotang) 
  (if (= lgtp "S") 
    (progn
      (setq cx cy 
            al bl 
            ggea ggeb)
    )
  ) 
  (if (= td "U") 
    (progn
      (if (and (= td "U") 
            (= ip "B")
          ) 
        (setq sp sp)
      ) 
      (if (and (= td "U") 
            (= ip "C")
          ) 
        (progn
          (setq sp (polar sp ang270 cx) 
                ep (polar ep ang270 cx))
        )
      ) 
      (if (and (= td "U") 
            (= ip "G")
          ) 
        (progn
          (setq sp (polar sp ang270 ggea) 
                ep (polar ep ang270 ggea))
        )
      ) 
      (setq p1 (polar sp ang90 al) 
            p2 (polar ep ang90 al) 
            p3 (polar sp ang90 th) 
            p4 (polar ep ang90 th))
    )
  ) 
  (if (= td "D") 
    (progn
      (if (and (= td "D") 
            (= ip "B")
          ) 
        (setq sp sp)
      ) 
      (if (and (= td "D") 
            (= ip "C")
          ) 
        (progn
          (setq sp (polar sp ang90 cx) 
                ep (polar ep ang90 cx))
        )
      ) 
      (if (and (= td "D") 
            (= ip "G")
          ) 
        (progn
          (setq sp (polar sp ang90 ggea) 
                ep (polar ep ang90 ggea))
        )
      ) 
      (setq p1 (polar sp ang270 al) 
            p2 (polar ep ang270 al) 
            p3 (polar sp ang270 th) 
            p4 (polar ep ang270 th))
    )
  ) 
  (if (= c_o 1 1) 
    (progn
      (setq cl_s (polar cl_s ang180 (* (getvar "dimscale") 15)) 
            cl_e (polar cl_e ang (* (getvar "dimscale") 15)))
      (setline "$cl") 
      (command "line" cl_s cl_e "")
    )
  ) 
  (if (= ta "A") 
    (progn
      (setline "$ol") 
      (command "line" sp p1 p2 ep "C") 
      (if (= d_o 1) 
        (progn
          (setline "$hl") 
          (command "line" p3 p4 "")
        )
      )
    )
  ) 
  (if (= ta "T") 
    (progn
      (setline "$ol") 
      (command "line" sp p1 p2 ep "C") 
      (if (= d_o 1) 
        (command "line" p3 p4 "")
      )
    )
  )
) 
(defun tfcsect (/ ip td sp ep p1 p2 p3 p4 p5 p6 p7) 
  (setq ip "T" td "R" 
        ck_2 1 
        ck_3 1 
        ck_4 1 
        ck_6 1)
  (mem_loc) 
  (setq cp (getpoint "\nLocation of beam:") 
        ang (dtr 90))
  (rotang) 
  (if (= ip "T") 
    (setq sp cp)
  ) 
  (if (= ip "C") 
    (setq sp (polar cp ang90 (/ bd 2.0)))
  ) 
  (if (= ip "B") 
    (setq sp (polar cp ang90 bd))
  ) 
  (if (= td "R") 
    (progn
      (setq p1 (polar sp ang fw) 
            p2 (polar p1 ang270 tth) 
            p3 (polar p2 ang185 slfw) 
            p4 (polar p3 ang270 wd) 
            p5 (polar p4 ang355 slfw) 
            p6 (polar p5 ang270 tth) 
            p7 (polar p6 ang180 fw))
      (marklent)
    )
  ) 
  (if (= td "L") 
    (progn
      (setq p1 (polar sp ang180 fw) 
            p2 (polar p1 ang270 tth) 
            p3 (polar p2 ang355 slfw) 
            p4 (polar p3 ang270 wd) 
            p5 (polar p4 ang185 slfw) 
            p6 (polar p5 ang270 tth) 
            p7 (polar p6 ang fw))
      (marklent)
    )
  ) 
  (setline "$ol") 
  (if (= d_o 1) 
    (command "pline" sp "w" "0" "0" p1 p2 "" "pline" p2 "w" "0" "0" p3 p4 p5 "" 
           "pline" p5 "w" "0" "0" p6 p7 sp "" "fillet" "r" rr "fillet" "P" p2 
           "pedit" p1 "j" p1 p2 p5 "" "x"
    )
  ) 
  (if (= d_o 0) 
    (command "pline" p1 "W" "0" "0" sp p7 p6 "")
  ) 
  (selsince) 
  (rotsect)
) 
(defun tfbsect (/ ip sp p1 p2 p3 p4 p5 p6 p7 p8 p9 p10 p11 p12) 
  (bm_ip) 
  (setq cp (getpoint "\nLocation of beam:") 
        ang (dtr 90))
  (rotang) 
  (cond
    ((= ip "TL") (setq sp (polar cp ang hfw))) 
    ((= ip "TC") (setq sp cp)) 
    ((= ip "TR") (setq sp (polar cp ang180 hfw))) 
    ((= ip "ML") (setq sp (polar (polar cp ang hfw) ang90 (/ bd 2.0)))) 
    ((= ip "MC") (setq sp (polar cp ang90 (/ bd 2.0)))) 
    ((= ip "MR") (setq sp (polar (polar cp ang180 hfw) ang90 (/ bd 2.0)))) 
    ((= ip "BL") (setq sp (polar (polar cp ang hfw) ang90 bd))) 
    ((= ip "BC") (setq sp (polar cp ang90 bd))) 
    ((= ip "BR") (setq sp (polar (polar cp ang180 hfw) ang90 bd)))
  ) 
  (setq p1 (polar sp ang hfw) 
        p2 (polar p1 ang270 tth) 
        p3 (polar p2 ang185 slfw) 
        p4 (polar p3 ang270 wd) 
        p5 (polar p4 ang355 slfw) 
        p6 (polar p5 ang270 tth) 
        p7 (polar p6 ang180 fw) 
        p8 (polar p7 ang90 tth) 
        p9 (polar p8 ang5 slfw) 
        p10 (polar p9 ang90 wd) 
        p11 (polar p10 ang175 slfw) 
        p12 (polar p11 ang90 tth))
  (marklent) 
  (setline "$ol") 
  (if (= d_o 1) 
    (command "pline" sp "w" "0" "0" p1 p2 "" "pline" p2 "w" "0" "0" p3 p4 p5 "" 
           "pline" p5 "w" "0" "0" p6 p7 p8 "" "pline" p8 "w" "0" "0" p9 p10 p11 
           "" "pline" p11 "w" "0" "0" p12 sp "" "fillet" "r" rr "fillet" "P" p2 
           "fillet" "r" rr "fillet" "p" p9 "pedit" p1 "j" p1 p2 p6 "" "x"
    )
  ) 
  (if (= d_o 0) 
    (progn
      (setq p13 (polar sp ang270 bd))
      (command "line" p1 p12 "" "line" p6 p7 "" "line" sp p13 "")
    )
  ) 
  (selsince) 
  (rotsect)
) 
(defun rhselev (/ p1 p2 p3 p4 p5 p6) 
  (setq ip "T" lgtp "L" 
        ck_2 1 
        ck_3 1 
        ck_4 1 
        ck_5 1 
        ck_6 1)
  (if (= chk_name "bhp_rhs") 
    (setq ck_6 0)
  ) 
  (mem_loc) 
  (setq sp (getpoint "\nStart point of beam:") 
        ep (getpoint sp "\nEnd point of beam:") 
        ang (angle sp ep) 
        cl_s sp 
        cl_e ep)
  (rotang) 
  (if (= lgtp "S") 
    (setq bd fw)
  ) 
  (if (= ip "T") 
    (setq sp sp)
  ) 
  (if (= ip "C") 
    (progn
      (setq sp (polar sp ang90 (/ bd 2.0)) 
            ep (polar ep ang90 (/ bd 2.0)))
    )
  ) 
  (if (= ip "B") 
    (progn
      (setq sp (polar sp ang90 bd) 
            ep (polar ep ang90 bd))
    )
  ) 
  (setq p1 (polar ep ang270 bd) 
        p2 (polar sp ang270 bd) 
        p3 (polar p2 ang90 th) 
        p4 (polar p1 ang90 th) 
        p5 (polar sp ang270 th) 
        p6 (polar ep ang270 th))
  (if (= c_o 1 1) 
    (progn
      (setq cl_s (polar cl_s ang180 (* (getvar "dimscale") 15)) 
            cl_e (polar cl_e ang (* (getvar "dimscale") 15)))
      (setline "$cl") 
      (command "line" cl_s cl_e "")
    )
  ) 
  (setline "$ol") 
  (command "line" ep sp p2 p1 "C") 
  (if (= d_o 1) 
    (progn
      (setline "$hl") 
      (command "line" p5 p6 "" "line" p3 p4 "")
    )
  )
) 
(defun rhssect (/ ip p1 p2 p3 p4 p5 p6 p7 p8 p9 p10 p11 p12 p13 p14 p15) 
  (bm_ip) 
  (setq cp (getpoint "\nLocation of beam:") 
        ang (dtr 90))
  (rotang) 
  (cond
    ((= ip "TL") (setq sp (polar cp ang fw))) 
    ((= ip "TC") (setq sp (polar cp ang (/ fw 2.0)))) 
    ((= ip "TR") (setq sp cp)) 
    ((= ip "ML") (setq sp (polar (polar cp ang90 (/ bd 2.0)) ang fw))) 
    ((= ip "MC") (setq sp (polar (polar cp ang90 (/ bd 2.0)) ang (/ fw 2.0)))) 
    ((= ip "MR") (setq sp (polar cp ang90 (/ bd 2.0)))) 
    ((= ip "BL") (setq sp (polar (polar cp ang90 bd) ang fw))) 
    ((= ip "BC") (setq sp (polar (polar cp ang90 bd) ang (/ fw 2.0)))) 
    ((= ip "BR") (setq sp (polar cp ang90 bd)))
  ) 
  (setq p1 (polar sp ang270 bd) 
        p2 (polar p1 ang180 fw) 
        p3 (polar p2 ang90 bd) 
        tp (polar sp ang180 th) 
        p4 (polar tp ang270 th) 
        p5 (polar p4 ang270 (- bd (* 2 th))) 
        p6 (polar p5 ang180 (- fw (* 2 th))) 
        p7 (polar p6 ang90 (- bd (* 2 th))))
  (marklent) 
  (setline "$ol") 
  (command "pline" sp "W" "0" "0" p1 p2 p3 "c") 
  (setvar "filletrad" tr)
  (command "fillet" "p" "l") 
  (if (= d_o 1) 
    (progn
      (setvar "filletrad" rr)
      (command "pline" p4 p5 p6 p7 "c" "fillet" "p" "l")
    )
  ) 
  (setvar "filletrad" 0)
  (selsince) 
  (rotsect)
) 
(defun chssect (/) 
  (setq cp (getpoint "\nLocation of chs:"))
  (setline "$ol") 
  (command "circle" cp o_r) 
  (if (= d_o 1) 
    (command "circle" cp i_r)
  ) 
  (princ)
) 
(defun lyscsect (/ ip td sp ep p1 p2 p3 p4 p5) 
  (setq ip "T" td "R" 
        ck_2 1 
        ck_3 1 
        ck_4 1 
        ck_6 1)
  (mem_loc) 
  (setq cp (getpoint "\nLocation of section:") 
        ang (dtr 90))
  (if (= ip "T") 
    (setq sp cp)
  ) 
  (if (= ip "C") 
    (setq sp (polar cp ang90 (/ bd 2.0)))
  ) 
  (if (= ip "B") 
    (setq sp (polar cp ang90 bd))
  ) 
  (if (= td "R") 
    (progn
      (setq p1 (polar sp ang fw) 
            p2 (polar p1 ang270 ft) 
            p3 (polar sp ang270 bd) 
            p4 (polar p3 ang fw) 
            p5 (polar p4 ang90 ft))
      (marklent)
    )
  ) 
  (if (= td "L") 
    (progn
      (setq p1 (polar sp ang180 fw) 
            p2 (polar p1 ang270 ft) 
            p3 (polar sp ang270 bd) 
            p4 (polar p3 ang180 fw) 
            p5 (polar p4 ang90 ft))
      (marklent)
    )
  ) 
;  (setvar "clayer" b#_psl)
;  (setline "$ol") 
  (command "pline" p2 "W" "0" "0" p1 sp p3 p4 p5 "") 
  (setvar "filletrad" 5)
  (command "fillet" "p" sp) 
  (selsince) 
  (rotsect)
) 
(defun lyszsect (/ ip td sp ep p1 p2 p3 p4 p5) 
  (setq ip "T" td "R" 
        ck_2 1 
        ck_3 1 
        ck_4 1 
        ck_6 1)
  (mem_loc) 
  (setq cp (getpoint "\nLocation of section:") 
        ang (dtr 90))
  (rotang) 
  (if (= ip "T") 
    (setq sp cp)
  ) 
  (if (= ip "C") 
    (setq sp (polar cp ang90 (/ bd 2.0)))
  ) 
  (if (= ip "B") 
    (setq sp (polar cp ang90 bd))
  ) 
  (if (= td "R") 
    (progn
      (setq p1 (polar sp ang fw) 
            p2 (polar p1 ang270 ft) 
            p3 (polar sp ang270 bd) 
            p4 (polar p3 ang180 fw) 
            p5 (polar p4 ang90 ft))
      (marklent)
    )
  ) 
  (if (= td "L") 
    (progn
      (setq p1 (polar sp ang180 fw) 
            p2 (polar p1 ang270 ft) 
            p3 (polar sp ang270 bd) 
            p4 (polar p3 ang fw) 
            p5 (polar p4 ang90 ft))
      (marklent)
    )
  ) 
 ; (setvar "clayer" b#_psl)
 ; (setline "$ol") 
  (command "pline" p2 "W" "0" "0" p1 sp p3 p4 p5 "") 
  (setvar "filletrad" 5)
  (command "fillet" "p" sp) 
  (selsince) 
  (rotsect)
) 
(defun lyszelev (/ p1 p2 p3 p4 p5 p6) 
  (setq ip "T" ta "A" 
        ck_2 1 
        ck_3 1 
        ck_5 1 
        ck_6 1)
  (mem_loc) 
  (setq sp (getpoint "\nStart point of beam:") 
        ep (getpoint sp "\nEnd point of beam:") 
        ang (angle sp ep) 
        cl_s sp 
        cl_e ep)
  (rotang) 
  (if (= ip "T") 
    (setq sp sp)
  ) 
  (if (= ip "C") 
    (progn
      (setq sp (polar sp ang90 (/ bd 2.0)) 
            ep (polar ep ang90 (/ bd 2.0)))
    )
  ) 
  (if (= ip "B") 
    (progn
      (setq sp (polar sp ang90 bd) 
            ep (polar ep ang90 bd))
    )
  ) 
  (setq p1 (polar ep ang270 bd) 
        p2 (polar sp ang270 bd) 
        p3 (polar p2 ang90 ft) 
        p4 (polar p1 ang90 ft) 
        p5 (polar sp ang270 ft) 
        p6 (polar ep ang270 ft))
 ; (setvar "clayer" b#_psl)
  (if (= c_o 1 1) 
    (progn
      (setq cl_s (polar cl_s ang180 (* (getvar "dimscale") 15)) 
            cl_e (polar cl_e ang (* (getvar "dimscale") 15)))
      (setline "$cl") 
      (command "line" cl_s cl_e "" "layer" "s" orglay "")
    )
  ) 
  (if (= ta "A") 
    (progn
      (setline "$ol") 
      (command "line" sp ep p1 p2 "C" "line" p3 p4 "") 
      (setline "$hl") 
      (command "line" p5 p6 "")
    )
  ) 
  (if (= ta "T") 
    (progn
      (setline "$ol") 
      (command "line" sp ep p1 p2 "C" "line" p5 p6 "") 
      (setline "$hl") 
      (command "line" p3 p4 "")
    )
  )
) 
(defun lyscplan (/ td ip sp ep P1 P2 P3 P4) 
  (setq td "U" ck_1 
        1 ck_2 
        1 ck_4 
        1 ck_5 
        1 ck_6 
        1)
  (mem_loc) 
  (setq sp (getpoint "\nStart point of beam:") 
        ep (getpoint sp "\nEnd point of beam:") 
        ang (angle sp ep))
  (rotang) 
 ; (setvar "clayer" b#_psl)
  (if (= td "U") 
    (progn
      (setq p1 (polar sp ang90 fw) 
            p2 (polar ep ang90 fw) 
            p3 (polar sp ang90 wt) 
            p4 (polar ep ang90 wt))
      (setline "$ol") 
      (command "line" sp p1 p2 ep "C") 
      (setline "$hl") 
      (command "line" p3 p4 "")
    )
  ) 
  (if (= td "D") 
    (progn
      (setq p1 (polar sp ang270 fw) 
            p2 (polar ep ang270 fw) 
            p3 (polar sp ang270 wt) 
            p4 (polar ep ang270 wt))
      (setline "$ol") 
      (command "line" sp p1 p2 ep "C") 
      (setline "$hl") 
      (command "line" p3 p4 "")
    )
  )
) 
(defun lyszplan (/ td ip sp ep P1 P2 P3 P4) 
  (setq td "U" ck_1 
        1 ck_2 
        1 ck_4 
        1 ck_5 
        1 ck_6 
        1)
  (mem_loc) 
  (setq sp (getpoint "\nStart point of beam:") 
        ep (getpoint sp "\nEnd point of beam:") 
        ang (angle sp ep))
  (rotang) 
;  (setvar "clayer" b#_psl)
  (if (= td "U") 
    (progn
      (setq p1 (polar sp ang90 fw) 
            p2 (polar ep ang90 fw) 
            p3 (polar sp ang90 wt) 
            p4 (polar ep ang90 wt) 
            p5 (polar sp ang270 fw) 
            p6 (polar ep ang270 fw))
      (setline "$ol") 
      (command "line" sp p1 p2 ep "C" "line" sp p5 p6 ep "") 
      (setline "$hl") 
      (command "line" p3 p4 "")
    )
  ) 
  (if (= td "D") 
    (progn
      (setq p1 (polar sp ang270 fw) 
            p2 (polar ep ang270 fw) 
            p3 (polar sp ang270 wt) 
            p4 (polar ep ang270 wt) 
            p5 (polar sp ang90 fw) 
            p6 (polar ep ang90 fw))
      (setline "$ol") 
      (command "line" sp p1 p2 ep "C" "line" sp p5 p6 ep "") 
      (setline "$hl") 
      (command "line" p3 p4 "")
    )
  )
) 
 
(defun mem_loc () 
  (new_dialog "mem_loc" bhp_dialog) 
  (mode_tile "b_ot" ck_1) 
  (mode_tile "c_en" ck_1) 
  (mode_tile "t_op" ck_1) 
  (mode_tile "a_ngb" ck_2) 
  (mode_tile "a_ngg" ck_2) 
  (mode_tile "a_ngc" ck_2) 
  (mode_tile "t_oed" ck_3) 
  (mode_tile "t_oeu" ck_3) 
  (mode_tile "t_oet" ck_4) 
  (mode_tile "t_oea" ck_4) 
  (mode_tile "t_oel" ck_5) 
  (mode_tile "t_oer" ck_5) 
  (mode_tile "l_egs" ck_6) 
  (mode_tile "l_egl" ck_6) 
  (set_tile "t_op" "1") 
  (set_tile "a_ngb" "1") 
  (set_tile "t_oeu" "1") 
  (set_tile "t_oea" "1") 
  (set_tile "t_oer" "1") 
  (set_tile "l_egl" "1") 
  (action_tile "t_op" "(setq ip \"T\")") 
  (action_tile "c_en" "(setq ip \"C\")") 
  (action_tile "b_ot" "(setq ip \"B\")") 
  (action_tile "a_ngb" "(setq ip \"B\")") 
  (action_tile "a_ngg" "(setq ip \"G\")") 
  (action_tile "a_ngc" "(setq ip \"C\")") 
  (action_tile "t_oeu" "(setq td \"U\")") 
  (action_tile "t_oed" "(setq td \"D\")") 
  (action_tile "t_oea" "(setq ta \"A\")") 
  (action_tile "t_oet" "(setq ta \"T\")") 
  (action_tile "t_oer" "(setq td \"R\")") 
  (action_tile "t_oel" "(setq td \"L\")") 
  (action_tile "l_egl" "(setq lgtp \"L\")") 
  (action_tile "l_egs" "(setq lgtp \"S\")") 
  (action_tile "cancel" "(done_dialog 0)") 
  (c_ont_dialog)
) 
(defun bm_ip () 
  (new_dialog "bm_ip" bhp_dialog) 
  (setq ip "TC")
  (set_tile "t_opc" "1") 
  (action_tile "t_opl" "(setq ip \"TL\")") 
  (action_tile "t_opc" "(setq ip \"TC\")") 
  (action_tile "t_opr" "(setq ip \"TR\")") 
  (action_tile "m_idl" "(setq ip \"ML\")") 
  (action_tile "m_idc" "(setq ip \"MC\")") 
  (action_tile "m_idr" "(setq ip \"MR\")") 
  (action_tile "b_otl" "(setq ip \"BL\")") 
  (action_tile "b_otc" "(setq ip \"BC\")") 
  (action_tile "b_otr" "(setq ip \"BR\")") 
  (action_tile "cancel" "(done_dialog 0)") 
  (c_ont_dialog)
) 
(defun c_ont_dialog () 
  (setq what_next (start_dialog))
  (if (= what_next 0) 
    (progn
      (*cancel*)
    )
  )
) 
(defun marklent () 
  (setq lastent (entlast))
) 
(defun selsince () 
  (setq ss2 nil 
        ss2 (ssadd) 
        e (entnext lastent))
  (while e 
    (ssadd e ss2) 
    (setq e (entnext e))
  )
) 
(defun setline (line) 
  (if (= line "$ol") 
    (progn
;    (setvar "cecolor" b#_olc)
;    (setvar "celtype" b#_olt)
      (if (= (tblsearch "layer" "035") nil)
		(command "layer" "new" "035" "")
		(command "layer" "set" "035" "")
	)
        ;(COMMAND "LAYER" "set" "035" "")
    )
  ) 
  (if (= line "$hl") 
    (progn
;     (setvar "cecolor" b#_hlc)
;     (setvar "celtype" b#_hlt)
      (if (= (tblsearch "layer" "hid") nil)
		(command "layer" "new" "hid" "")
		(command "layer" "set" "hid" "")
	)
        ;(COMMAND "LAYER" "SET" "hid" "")
    )
  ) 
  (if (= line "$cl") 
    (progn
;     (setvar "cecolor" b#_clc)
;     (setvar "celtype" b#_hlt)
      (if (= (tblsearch "layer" "centre") nil)
		(command "layer" "new" "centre" "")
		(command "layer" "set" "centre" "")
	)
        ;(COMMAND "LAYER" "SET" "centre" "")
    )
  )
) 
(defun rotsect () 
  (prompt "\nRotation angle:") 
  (command "rotate" ss2 "" cp pause)
) 
(prompt "\n") 

(princ)
